# TRC Overlay Specefication
Author: Martin Wagner

# Specification: Specification Document
- Description: TRC Overlay Specification

## R-01
- PlainText: Die IDs und die textuellen Kurzbeschreibungen der einer Quellcodedatei zugeordneten Requirements sollen in einem zusätzlichen Fenster angezeigt werden.

## R-02
- PlainText: Die Zuordnung von Requirements zu einer Quellcodedatei soll mit dem Tool durch den Nutzer erfolgen können.

## R-03
- PlainText: Die textuelle Kurzbeschreibung der Requirements soll aus einer Datei im gängigen Standardformat für Requirements-Management, ReqIF bezogen werden.

## R-04
- PlainText: Das zusätzliche Fenster soll Knöpfe zum Auslösen von Funktionen des Tools enthalten.

## R-05
- PlainText: Die Bereiche im Quellcode, die mit Traceability-Informationen annotiert sind, werden durch rechteckige Boxen repräsentiert.

## R-06
- PlainText: Boxen sollen durch Selektion von Quellcode durch den Nutzer und anschließenden Knopfdruck angelegt werden können. Dabei sollen die Boxen automatisch vom Tool zu ausgewählten Requirements zugeordnet werden.

## R-07
- PlainText: Eine Box soll genau einem Requirement zugeordnet sein.

## R-08
- PlainText: Die Boxen sollen beliebige Start und Endpunkte im Quellcode haben können.

## R-09
- PlainText: Die Boxen sollen beim ersten Zeichen, das kein Leerzeichen oder ein Tabulator ist, in der ersten Zeile der Box beginnen.

## R-10
- PlainText: Die Boxen sollen beim letzten markierten Zeichen einer Zeile, das kein Leerzeichen oder Tabulator ist, enden.

## R-11
- PlainText: Boxen sollen eine Mindestgröße von einem Zeichen haben

## R-12
- PlainText: Die Boxen sollen sich automatisch an die maximale Breite des eingeschlossenen Textes anpassen.

## R-13
- PlainText: Bei einer Änderung im Quellcode sollen die von der Änderung betroffen Boxen automatisch vom Tool angepasst werden.

## R-14
- PlainText: Gibt es noch keine Box an der Stelle der Änderung, so sollen neue Boxen angelegt werden, entsprechend der im zusätzlichen Fenster ausgewählten Requirements.

## R-15
- PlainText: Wird eine Box durch eine Änderung auf eine Länge kleiner gleich 0 reduziert, so soll die Box entfernt werden.

## R-16
- PlainText: Für die visuelle Zuordnung zwischen Boxen und Requirements wird das Medium "Hintergrundfarbe" gewählt.

## R-17
- PlainText: Das Tool soll farbige Boxen im Editor der IDE anzeigen können.

## R-18
- PlainText: Angezeigte Requirements und die zugehörigen Boxen müssen in der gleichen Farbe gekennzeichnet werden.

## R-19
- PlainText: Die Farbe von Requirements und deren zugehörigen Boxen soll vom Nutzer geändert werden können.

## R-20
- PlainText: Wenn ein neues Requirement zu einer Quellcodedatei hinzugefügt wird, soll dem Requirement vom Tool einmalig eine zufällige Farbe zugewiesen werden.

## R-21
- PlainText: Die Farbe eines Requirements soll nach dem ersten Zuweisen gespeichert werden.

## R-22
- PlainText: Die zufällige, einem hinzugefügten Requirement zugewiesene Farbe (siehe R-20) soll eine Pastellfarbe sein.
- CrossRefLink -> R-22
- CrossRefLink -> R-20

## R-23
- PlainText: Das Tool soll den Benutzer motivieren, ebendieses benutzen zu wollen. Dazu soll es die Benutzeroberfläche des Nutzers visuell bereichern
- implement: false

## R-24
- PlainText: Die Antwortzeiten für die unterschiedlichen Funktionen des Tools sollen jeweils maximal 0,5 Sekunden betragen.
- implement: false

## R-25
- PlainText: Implementierter Quellcode dieses Prototypen soll dokumentiert sein.
- implement: false

## R-26
- PlainText: Das Tool soll unabhängig von der Programmiersprache sein, in welcher der Programmierer arbeitet.

## R-27
- PlainText: Der Anwender soll seinen Fokus mittels eines Layer-Systems auf vom Anwender ausgewählte Requirements setzen können

## R13
