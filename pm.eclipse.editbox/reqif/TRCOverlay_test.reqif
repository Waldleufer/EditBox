# TRC Overlay Specefication
Author: Martin Wagner

# Specification: Specification Document
- Description: TRC Overlay Specification

## R-01
- PlainText: Das TRC Overlay soll farbige Boxen erzeugen können.

### R-01a
- PlainText: Die Boxen sollen frei im Code positionierbar sein.

### R-01b
- PlainText: Die Boxen sollen sich automatisch an die maximale Breite des eingeschlossenen Textes anpassen.

## R-02
- PlainText: Das TRC Overlay soll farbige Boxen darstellen können

### R-02a
- PlainText: Boxen in einer bestimmten Farbe sollen zu einem Requirement in der gleichen Farbe gehören.

### R-02b
- PlainText: Eine Änderung der Farbe (von Requirement und zugehörigen Boxen) soll möglich sein.

### R-02c
- PlainText: Der Anwender soll seinen Fokus mittels eines Layer Systems auf bestimmte Requirements legen können.

## R-03
- PlainText: Nur die in der Quellcode Datei verwendeten oder zu verwendenden Requirements sollen angezeigt werden.

### R-03a
- PlainText: Zusätzliche Requirements sollen zu dieser Auswahl hinzugefügt werden können und bestehende Requirements sollen entfernt werden können.

### R-03b
- PlainText: Das Entfernen von Requirements soll nur möglich sein, wenn keine Quellcodeabschnitte mehr auf dieses Requirement verweisen.

## R-04
- PlainText: Zusätzliche Daten zu den Requirements sollen angezeigt werden können.

### R-04a
- PlainText: Die zusätzlichen Daten für die Requirements (ID und Information) sollen aus einer Datei im gängigen Standard für Anforderungsverwaltung, ReqIF bezogen werden.

### R-04b
- PlainText: Die ID und textuelle Information zum Requirement mit dieser ID sollen angezeigt werden können.

## R-05
- PlainText: Das Markieren von Quellcode und Zuweisen der Selektion zu keinem, einem oder mehreren Requirements soll möglich sein.
